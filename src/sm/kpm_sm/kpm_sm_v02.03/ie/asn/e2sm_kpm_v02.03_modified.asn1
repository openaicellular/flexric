-- **************************************************************
-- E2SM-KPM Information Element Definitions
-- **************************************************************

E2SM-KPM-IEs {
iso(1) identified-organization(3) dod(6) internet(1) private(4) enterprise(1) oran(53148) e2(1) version2(2) e2sm(2) e2sm-KPMMON-IEs (2)}

DEFINITIONS AUTOMATIC TAGS ::= 

BEGIN

-- **************************************************************
--   IEs
-- **************************************************************

IMPORTS
        CGI,
        FiveQI,
        PLMNIdentity,
        QCI,
        QosFlowIdentifier,
        RANfunction-Name,
        RIC-Format-Type,
        RIC-Style-Name,
        RIC-Style-Type,
        S-NSSAI,
        UEID
FROM E2SM-COMMON-IEs;

TimeStamp ::= OCTET STRING (SIZE(4))

BinIndex ::= INTEGER (1.. 65535, ...)

BinRangeValue ::= CHOICE {
        valueInt                                INTEGER,
        valueReal                       REAL,
        ...
}

GranularityPeriod ::= INTEGER (1.. 4294967295)

LogicalOR ::= ENUMERATED {true, ...}

MeasurementType ::= CHOICE {
        measName                                MeasurementTypeName,
        measID                          MeasurementTypeID,
        ...
}

MeasurementTypeName ::= PrintableString(SIZE(1.. 150, ...))

MeasurementTypeID ::= INTEGER (1.. 65536, ...)

MeasurementLabel ::= SEQUENCE {
        noLabel                                 ENUMERATED {true, ...}                          OPTIONAL,
        plmnID                                  PLMNIdentity                                            OPTIONAL,
        sliceID                                 S-NSSAI                                                         OPTIONAL,
        fiveQI                                  FiveQI                                                          OPTIONAL,
        qFI                                             QosFlowIdentifier                                       OPTIONAL,
        qCI                                             QCI                                                                     OPTIONAL,
        qCImax                                  QCI                                                                     OPTIONAL,
        qCImin                                  QCI                                                                     OPTIONAL,
        aRPmax                                  INTEGER (1.. 15, ...)                           OPTIONAL,
        aRPmin                                  INTEGER (1.. 15, ...)                           OPTIONAL,
        bitrateRange                    INTEGER (1.. 65535, ...)                        OPTIONAL,
        layerMU-MIMO                    INTEGER (1.. 65535, ...)                        OPTIONAL,
        sUM                                             ENUMERATED {true, ...}                          OPTIONAL,
        distBinX                                INTEGER (1.. 65535, ...)                    OPTIONAL,
        distBinY                                INTEGER (1.. 65535, ...)                    OPTIONAL,
        distBinZ                                INTEGER (1.. 65535, ...)                    OPTIONAL,
        preLabelOverride                ENUMERATED {true, ...}                          OPTIONAL,
        startEndInd                             ENUMERATED {start, end, ...}            OPTIONAL,
        min                                             ENUMERATED {true, ...}                          OPTIONAL,
        max                                             ENUMERATED {true, ...}                          OPTIONAL,
        avg                                             ENUMERATED {true, ...}                          OPTIONAL,
        ...,
        ssbIndex                                INTEGER (1.. 65535, ...)                        OPTIONAL,
        nonGoB-BFmode-Index         INTEGER (1.. 65535, ...)                    OPTIONAL,
        mIMO-mode-Index             INTEGER (1.. 2, ...)                                OPTIONAL
}

TestCondInfo ::= SEQUENCE{
        testType                                TestCond-Type,
        testExpr                                TestCond-Expression                                             OPTIONAL,
        testValue                           TestCond-Value                                                      OPTIONAL,
        ...
}

TestCond-Type ::= CHOICE{
        gBR                                     ENUMERATED {true, ...},
        aMBR                            ENUMERATED {true, ...},
        isStat                          ENUMERATED {true, ...},
        isCatM                          ENUMERATED {true, ...},
        rSRP                            ENUMERATED {true, ...},
        rSRQ                            ENUMERATED {true, ...},
        ul-rSRP                         ENUMERATED {true, ...},
        cQI                                     ENUMERATED {true, ...},
        fiveQI                          ENUMERATED {true, ...},
        qCI                                     ENUMERATED {true, ...},
        sNSSAI                          ENUMERATED {true, ...},
        ...
}

TestCond-Expression ::= ENUMERATED {
equal, 
greaterthan, 
lessthan, 
contains, 
present, 
...
}

TestCond-Value ::= CHOICE{
        valueInt                        INTEGER,
        valueEnum                       INTEGER,
        valueBool                       BOOLEAN,
        valueBitS                       BIT STRING,
        valueOctS                       OCTET STRING, 
        valuePrtS                       PrintableString,
        valueReal                       REAL,
        ...
}

-- **************************************************************
--   Lists
-- **************************************************************

maxnoofCells                            INTEGER ::= 16384
maxnoofRICStyles                        INTEGER ::= 63
maxnoofMeasurementInfo          INTEGER ::= 65535
maxnoofLabelInfo                        INTEGER ::= 2147483647
maxnoofMeasurementRecord        INTEGER ::= 65535
maxnoofMeasurementValue         INTEGER ::= 2147483647
maxnoofConditionInfo            INTEGER ::= 32768
maxnoofUEID                                     INTEGER ::= 65535
maxnoofConditionInfoPerSub      INTEGER ::= 32768
maxnoofUEIDPerSub                       INTEGER ::= 65535
maxnoofUEMeasReport                     INTEGER ::= 65535
maxnoofBin                                      INTEGER ::= 65535

BinRangeDefinition ::= SEQUENCE {
binRangeListX           BinRangeList, 
binRangeListY           BinRangeList                    OPTIONAL -- This IE shall not be present for a distribution measurement type that doesn't use Distribution Bin Y --,
binRangeListZ           BinRangeList                    OPTIONAL -- This IE shall not be present for a distribution measurement type that doesn't use Distribution Bin Z --,
...
}

BinRangeList ::= SEQUENCE (SIZE(1..maxnoofBin)) OF BinRangeItem

BinRangeItem ::= SEQUENCE {
        binIndex                                BinIndex,
        startValue                          BinRangeValue,
        endValue                                BinRangeValue,
        ...
}

DistMeasurementBinRangeList ::= SEQUENCE (SIZE(1..maxnoofMeasurementInfo)) OF DistMeasurementBinRangeItem

DistMeasurementBinRangeItem ::= SEQUENCE {
        measType                                MeasurementType,
        binRangeDef                         BinRangeDefinition,
        ...
}

MeasurementInfoList ::= SEQUENCE (SIZE(1..maxnoofMeasurementInfo)) OF MeasurementInfoItem

MeasurementInfoItem ::= SEQUENCE {
        measType                                MeasurementType,
        labelInfoList               LabelInfoList,
        ...
}

LabelInfoList ::= SEQUENCE (SIZE(1..maxnoofLabelInfo)) OF LabelInfoItem

LabelInfoItem ::= SEQUENCE {
        measLabel                           MeasurementLabel,
        ...
}

MeasurementData ::= SEQUENCE (SIZE(1..maxnoofMeasurementRecord)) OF MeasurementDataItem

MeasurementDataItem ::= SEQUENCE {
measRecord                                  MeasurementRecord,
incompleteFlag                      ENUMERATED {true, ...}                                      OPTIONAL,
...
}

MeasurementRecord ::= SEQUENCE (SIZE(1..maxnoofMeasurementValue)) OF MeasurementRecordItem

MeasurementRecordItem ::= CHOICE {
        integer                             INTEGER (0.. 4294967295),
        real                                    REAL,
        noValue                             NULL,
        ...
}

MeasurementInfo-Action-List ::= SEQUENCE (SIZE(1..maxnoofMeasurementInfo)) OF MeasurementInfo-Action-Item

MeasurementInfo-Action-Item ::= SEQUENCE {
        measName                                MeasurementTypeName,
        measID                              MeasurementTypeID                   OPTIONAL,
        ...,
        binRangeDef                         BinRangeDefinition                  OPTIONAL
}

MeasurementCondList ::= SEQUENCE (SIZE(1..maxnoofMeasurementInfo)) OF MeasurementCondItem

MeasurementCondItem ::= SEQUENCE {
        measType                                MeasurementType,
        matchingCond                MatchingCondList,
        binRangeDef                         BinRangeDefinition                  OPTIONAL,
        ...
}

MeasurementCondUEidList ::= SEQUENCE (SIZE(1..maxnoofMeasurementInfo)) OF MeasurementCondUEidItem

MeasurementCondUEidItem ::= SEQUENCE {
        measType                                MeasurementType,
        matchingCond                    MatchingCondList,
        matchingUEidList                MatchingUEidList                        OPTIONAL,
        matchingUEidPerGP               MatchingUEidPerGP                       OPTIONAL,
        ...
}

MatchingCondList ::= SEQUENCE (SIZE(1..maxnoofConditionInfo)) OF MatchingCondItem

MatchingCondItem ::= SEQUENCE {
matchingCondChoice              MatchingCondItem-Choice,
logicalOR                                   LogicalOR                                   OPTIONAL,
...
}

MatchingCondItem-Choice ::= CHOICE{
        measLabel                           MeasurementLabel,
        testCondInfo                TestCondInfo,
        ...
}

MatchingUEidList ::= SEQUENCE (SIZE(1..maxnoofUEID)) OF MatchingUEidItem

MatchingUEidItem ::= SEQUENCE{
        ueID                                    UEID,
        ...
}

MatchingUEidPerGP ::= SEQUENCE (SIZE(1..maxnoofMeasurementRecord)) OF MatchingUEidPerGP-Item

MatchingUEidPerGP-Item ::= SEQUENCE{
        matchedPerGP                            CHOICE{
                noUEmatched                     ENUMERATED {true, ...},
                oneOrMoreUEmatched              MatchingUEidList-PerGP,
                ...
        },
        ...
}

MatchingUEidList-PerGP ::= SEQUENCE (SIZE(1..maxnoofUEID)) OF MatchingUEidItem-PerGP

MatchingUEidItem-PerGP ::= SEQUENCE{
        ueID                                    UEID,
        ...
}


MatchingUeCondPerSubList ::= SEQUENCE (SIZE(1..maxnoofConditionInfoPerSub)) OF MatchingUeCondPerSubItem

MatchingUeCondPerSubItem ::= SEQUENCE{
        testCondInfo            TestCondInfo,
        ...,
        logicalOR                       LogicalOR                               OPTIONAL
}

MatchingUEidPerSubList ::= SEQUENCE (SIZE(2..maxnoofUEIDPerSub)) OF MatchingUEidPerSubItem

MatchingUEidPerSubItem ::= SEQUENCE{
        ueID                               UEID,
        ...
}

UEMeasurementReportList ::= SEQUENCE (SIZE(1..maxnoofUEMeasReport)) OF UEMeasurementReportItem

UEMeasurementReportItem ::= SEQUENCE{
        ueID                               UEID,
        measReport                     E2SM-KPM-IndicationMessage-Format1,
        ...
}



-- **************************************************************
-- E2SM-KPM Service Model IEs
-- **************************************************************

-- **************************************************************
--   Event Trigger Definition OCTET STRING contents
-- **************************************************************

E2SM-KPM-EventTriggerDefinition ::= SEQUENCE{
        eventDefinition-formats                 CHOICE{
                eventDefinition-Format1         E2SM-KPM-EventTriggerDefinition-Format1,
                ...
        },
        ...
}

E2SM-KPM-EventTriggerDefinition-Format1 ::= SEQUENCE{
        reportingPeriod                                 INTEGER (1.. 4294967295),
        ...
}

-- **************************************************************
--   Action Definition OCTET STRING contents
-- **************************************************************

E2SM-KPM-ActionDefinition ::= SEQUENCE{
        ric-Style-Type                                  RIC-Style-Type,
        actionDefinition-formats        CHOICE{
                actionDefinition-Format1                E2SM-KPM-ActionDefinition-Format1,
                actionDefinition-Format2                E2SM-KPM-ActionDefinition-Format2,
                actionDefinition-Format3                E2SM-KPM-ActionDefinition-Format3,
                actionDefinition-Format4                E2SM-KPM-ActionDefinition-Format4,
                actionDefinition-Format5                E2SM-KPM-ActionDefinition-Format5,
                ...
        },
        ...
}

E2SM-KPM-ActionDefinition-Format1 ::= SEQUENCE {
        measInfoList                                    MeasurementInfoList,
        granulPeriod                                    GranularityPeriod,
        cellGlobalID                                    CGI                                                     OPTIONAL,
        distMeasBinRangeInfo                    DistMeasurementBinRangeList             OPTIONAL,
        ...
}

E2SM-KPM-ActionDefinition-Format2 ::= SEQUENCE {
        ueID                                                    UEID,
        subscriptInfo                                   E2SM-KPM-ActionDefinition-Format1,
        ...
}

E2SM-KPM-ActionDefinition-Format3 ::= SEQUENCE {
        measCondList                                    MeasurementCondList,
        granulPeriod                                    GranularityPeriod,
        cellGlobalID                                    CGI                                                         OPTIONAL,
        ...
}

E2SM-KPM-ActionDefinition-Format4 ::= SEQUENCE {
        matchingUeCondList                          MatchingUeCondPerSubList,
        subscriptionInfo                                E2SM-KPM-ActionDefinition-Format1,
        ...
}

E2SM-KPM-ActionDefinition-Format5 ::= SEQUENCE {
        matchingUEidList                                MatchingUEidPerSubList,
        subscriptionInfo                                E2SM-KPM-ActionDefinition-Format1,
        ...
}


-- **************************************************************
--   Indication Header OCTET STRING contents
-- **************************************************************

E2SM-KPM-IndicationHeader ::= SEQUENCE{
        indicationHeader-formats                CHOICE{
                indicationHeader-Format1                E2SM-KPM-IndicationHeader-Format1,
                ...
        },
        ...
}

E2SM-KPM-IndicationHeader-Format1 ::= SEQUENCE{
        colletStartTime                             TimeStamp,
        fileFormatversion                               PrintableString (SIZE (0..15), ...)             OPTIONAL,
        senderName                                              PrintableString (SIZE (0..400), ...)    OPTIONAL,
        senderType                                              PrintableString (SIZE (0..8), ...)              OPTIONAL,
        vendorName                                              PrintableString (SIZE (0..32), ...)             OPTIONAL,
        ...
}

-- **************************************************************
--   Indication Message OCTET STRING contents
-- **************************************************************

E2SM-KPM-IndicationMessage ::= SEQUENCE{
        indicationMessage-formats               CHOICE{
                indicationMessage-Format1               E2SM-KPM-IndicationMessage-Format1,
                indicationMessage-Format2               E2SM-KPM-IndicationMessage-Format2,
                indicationMessage-Format3               E2SM-KPM-IndicationMessage-Format3,
                ...
        },
        ...
}

E2SM-KPM-IndicationMessage-Format1 ::= SEQUENCE {
        measData                                                        MeasurementData,
        measInfoList                                        MeasurementInfoList                                         OPTIONAL,
        granulPeriod                                        GranularityPeriod                                           OPTIONAL,
        ...
}

E2SM-KPM-IndicationMessage-Format2 ::= SEQUENCE {
        measData                                                        MeasurementData,
        measCondUEidList                                    MeasurementCondUEidList,
        granulPeriod                                        GranularityPeriod                                           OPTIONAL,
        ...
}

E2SM-KPM-IndicationMessage-Format3 ::= SEQUENCE {
        ueMeasReportList                                    UEMeasurementReportList,
        ...
}


-- ***************************************************************
--   RAN Function Definition OCTET STRING contents
-- ***************************************************************

E2SM-KPM-RANfunction-Description ::= SEQUENCE{
        ranFunction-Name                                        RANfunction-Name,
        ric-EventTriggerStyle-List                  SEQUENCE (SIZE(1..maxnoofRICStyles)) OF RIC-EventTriggerStyle-Item          OPTIONAL,
        ric-ReportStyle-List                            SEQUENCE (SIZE(1..maxnoofRICStyles)) OF RIC-ReportStyle-Item                    OPTIONAL,
        ...
}

RIC-EventTriggerStyle-Item ::= SEQUENCE{
        ric-EventTriggerStyle-Type                      RIC-Style-Type,
        ric-EventTriggerStyle-Name                      RIC-Style-Name,
        ric-EventTriggerFormat-Type                 RIC-Format-Type,
        ...
}

RIC-ReportStyle-Item ::= SEQUENCE{
        ric-ReportStyle-Type                            RIC-Style-Type,
        ric-ReportStyle-Name                            RIC-Style-Name,
        ric-ActionFormat-Type                           RIC-Format-Type,
        measInfo-Action-List                            MeasurementInfo-Action-List, 
        ric-IndicationHeaderFormat-Type         RIC-Format-Type,
        ric-IndicationMessageFormat-Type        RIC-Format-Type,
        ...
}

END

--   **************************************************************
--   E2SM
--   Information Element Definitions
--
--   **************************************************************
E2SM-COMMON-IEs {
iso(1) identified-organization(3) dod(6) internet(1) private(4) enterprise(1) 53148 e2(1) version1
(1) e2sm(2) e2sm-COMMON-IEs (0)}
DEFINITIONS AUTOMATIC TAGS ::=
BEGIN
-- --------------------------------------------------
-- Constants
-- --------------------------------------------------
maxE1APid                       INTEGER ::= 65535
maxF1APid                       INTEGER ::= 4
-- IEs derived from 3GPP 36.423 (X2AP)
maxEARFCN               INTEGER ::= 65535
-- IEs derived from 3GPP 38.473 (F1AP)
maxNRARFCN              INTEGER ::= 3279165
maxnoofNrCellBands      INTEGER ::= 32
-- --------------------------------------------------
-- E2SM Commmon IEs
-- --------------------------------------------------
CGI ::= CHOICE {
    nR-CGI                           NR-CGI,
    eUTRA-CGI                        EUTRA-CGI,
    ...
}
CoreCPID ::= CHOICE {
    fiveGC                           GUAMI,
    ePC                              GUMMEI,
    ...
}
InterfaceIdentifier ::= CHOICE {
    nG                  InterfaceID-NG,
    xN                  InterfaceID-Xn,
    f1                  InterfaceID-F1,
    e1                  InterfaceID-E1,
    s1                  InterfaceID-S1,
    x2                  InterfaceID-X2,
    w1                  InterfaceID-W1,
    ...
}
InterfaceID-NG ::= SEQUENCE {
    guami                   GUAMI,
    ...
}
InterfaceID-Xn ::= SEQUENCE {
    global-NG-RAN-ID        GlobalNGRANNodeID,
    ...
}
InterfaceID-F1 ::= SEQUENCE {
    globalGNB-ID            GlobalGNB-ID,
    gNB-DU-ID               GNB-DU-ID,
    ...
}
InterfaceID-E1 ::= SEQUENCE {
    globalGNB-ID            GlobalGNB-ID,
    gNB-CU-UP-ID            GNB-CU-UP-ID,
    ...
}
InterfaceID-S1 ::= SEQUENCE {
    gUMMEI                  GUMMEI,
    ...
}
InterfaceID-X2 ::= SEQUENCE {
    nodeType                CHOICE {
        global-eNB-ID           GlobalENB-ID,
        global-en-gNB-ID        GlobalenGNB-ID,
        ...
    },
    ...
}
InterfaceID-W1 ::= SEQUENCE {
    global-ng-eNB-ID                       GlobalNgENB-ID,
    ng-eNB-DU-ID                           NGENB-DU-ID,
    ...
}
Interface-MessageID ::= SEQUENCE {
    interfaceProcedureID        INTEGER,
    messageType                 ENUMERATED {initiatingMessage, successfulOutcome,
unsuccessfulOutcome, ...},
    ...
}
InterfaceType ::= ENUMERATED {nG, xn, f1, e1, s1, x2, w1, ...}
GroupID ::= CHOICE {
    fiveGC                                 FiveQI,
    ePC                                    QCI,
    ...
}
QoSID ::= CHOICE {
    fiveGC                                 FiveQI,
    ePC                                    QCI,
    ...
}
RANfunction-Name ::= SEQUENCE{
    ranFunction-ShortName                  PrintableString(SIZE(1..150,...)),
    ranFunction-E2SM-OID                   PrintableString(SIZE(1..1000,...)),
    ranFunction-Description                PrintableString(SIZE(1..150,...)),
    ranFunction-Instance                   INTEGER                                               OPTIONAL,
    ...
}
RIC-Format-Type ::= INTEGER
RIC-Style-Type ::= INTEGER
RIC-Style-Name ::= PrintableString(SIZE(1..150,...))
RRC-MessageID ::= SEQUENCE {
    rrcType         CHOICE {
        lTE             RRCclass-LTE,
        nR              RRCclass-NR,
         ...
     },
     messageID            INTEGER,
     ...
}
RRCclass-LTE ::= ENUMERATED {bCCH-BCH, bCCH-BCH-MBMS, bCCH-DL-SCH, bCCH-DL-SCH-BR, bCCH-DL-SCH-MBMS,
mCCH, pCCH, dL-CCCH, dL-DCCH, uL-CCCH, uL-DCCH, sC-MCCH, ...}
RRCclass-NR ::= ENUMERATED {bCCH-BCH, bCCH-DL-SCH, dL-CCCH, dL-DCCH, pCCH, uL-CCCH, uL-CCCH1, uL-DCCH, ...}
ServingCell-ARFCN ::= CHOICE {
    nR                  NR-ARFCN,
    eUTRA               E-UTRA-ARFCN,
    ...
}
ServingCell-PCI ::= CHOICE {
    nR                  NR-PCI,
    eUTRA               E-UTRA-PCI,
    ...
}
UEID ::= CHOICE{
    gNB-UEID                    UEID-GNB,
    gNB-DU-UEID                 UEID-GNB-DU,
    gNB-CU-UP-UEID              UEID-GNB-CU-UP,
    ng-eNB-UEID                 UEID-NG-ENB,
    ng-eNB-DU-UEID              UEID-NG-ENB-DU,
    en-gNB-UEID                 UEID-EN-GNB,
    eNB-UEID                    UEID-ENB,
    ...
}
UEID-GNB ::= SEQUENCE{
    amf-UE-NGAP-ID              AMF-UE-NGAP-ID,
    guami                       GUAMI,
    gNB-CU-UE-F1AP-ID-List      UEID-GNB-CU-F1AP-ID-List        OPTIONAL,
-- C-ifCUDUseparated: This IE shall be present in messages from E2 Node to NearRT-RIC for a CU-DU separated gNB, whereas from NearRT-RIC to E2 Node messages, this IE may not be included. More than 1 F1AP ID shall be reported by E2 Node only when NR-DC is established.
    gNB-CU-CP-UE-E1AP-ID-List   UEID-GNB-CU-CP-E1AP-ID-List     OPTIONAL,
-- C-ifCPUPseparated: This IE shall be present in messages from E2 Node to NearRT-RIC for a CP-UP separated gNB, whereas from NearRT-RIC to E2 Node messages, this IE may not be included.
    ran-UEID                    RANUEID                         OPTIONAL,
    m-NG-RAN-UE-XnAP-ID         NG-RANnodeUEXnAPID              OPTIONAL,
-- C-ifDCSetup: This IE shall be present in messages from E2 Node to NearRT-RIC if DC is established, whereas from NearRT-RIC to E2 Node messages, this IE may not be included. To be reported by both MN and SN.
    globalGNB-ID                GlobalGNB-ID                    OPTIONAL,
-- This IE shall not be used. This IE is replaced with globalNG-RANNode-ID.
    ...,
    globalNG-RANNode-ID         GlobalNGRANNodeID               OPTIONAL
-- C-ifDCSetup: This IE shall be present in messages from E2 Node to NearRT-RIC if DC is established, whereas from NearRT-RIC to E2 Node messages, this IE may not be included. To be reported only by SN.
}
UEID-GNB-CU-CP-E1AP-ID-List ::= SEQUENCE (SIZE(1..maxE1APid)) OF UEID-GNB-CU-CP-E1AP-ID-Item
UEID-GNB-CU-CP-E1AP-ID-Item ::= SEQUENCE{
    gNB-CU-CP-UE-E1AP-ID    GNB-CU-CP-UE-E1AP-ID,
    ...
}
UEID-GNB-CU-F1AP-ID-List ::= SEQUENCE (SIZE(1..maxF1APid)) OF UEID-GNB-CU-CP-F1AP-ID-Item
UEID-GNB-CU-CP-F1AP-ID-Item ::= SEQUENCE{
    gNB-CU-UE-F1AP-ID       GNB-CU-UE-F1AP-ID,
    ...
}
UEID-GNB-DU ::= SEQUENCE{
    gNB-CU-UE-F1AP-ID                GNB-CU-UE-F1AP-ID,
    ran-UEID                         RANUEID                                    OPTIONAL,
    ...
}
UEID-GNB-CU-UP ::= SEQUENCE{
    gNB-CU-CP-UE-E1AP-ID    GNB-CU-CP-UE-E1AP-ID,
    ran-UEID                RANUEID                                             OPTIONAL,
    ...
}
UEID-NG-ENB ::= SEQUENCE{
    amf-UE-NGAP-ID          AMF-UE-NGAP-ID,
    guami                   GUAMI,
    ng-eNB-CU-UE-W1AP-ID    NGENB-CU-UE-W1AP-ID             OPTIONAL,
-- C-ifCUDUseperated: This IE shall be present in messages from E2 Node to NearRT-RIC for a CU-DU seperated ng-eNB, whereas from NearRT-RIC to E2 Node messages, this IE may not be included.
    m-NG-RAN-UE-XnAP-ID     NG-RANnodeUEXnAPID              OPTIONAL,
-- C-ifDCSetup: This IE shall be present in messages from E2 Node to NearRT-RIC if DC is established, whereas from NearRT-RIC to E2 Node messages, this IE may not be included. To be reported by both MN and SN.
    globalNgENB-ID          GlobalNgENB-ID                  OPTIONAL,
-- This IE shall not be used. This IE is replaced with globalNG-RANNode-ID.
    ...,
    globalNG-RANNode-ID         GlobalNGRANNodeID           OPTIONAL
-- C-ifDCSetup: This IE shall be present in messages from E2 Node to NearRT-RIC if DC is established, whereas from NearRT-RIC to E2 Node messages, this IE may not be included. To be reported only by SN.
}
UEID-NG-ENB-DU ::= SEQUENCE{
    ng-eNB-CU-UE-W1AP-ID    NGENB-CU-UE-W1AP-ID,
    ...
}
UEID-EN-GNB ::= SEQUENCE{
    m-eNB-UE-X2AP-ID            ENB-UE-X2AP-ID,
    m-eNB-UE-X2AP-ID-Extension ENB-UE-X2AP-ID-Extension     OPTIONAL,
    globalENB-ID                GlobalENB-ID,
    gNB-CU-UE-F1AP-ID           GNB-CU-UE-F1AP-ID           OPTIONAL,
-- C-ifCUDUseperated: This IE shall be present in messages from E2 Node to                           NearRT-RIC for a CU-DU seperated en-gNB, whereas from NearRT-RIC to E2 Node messages, this IE may                           not be included.
    gNB-CU-CP-UE-E1AP-ID-List   UEID-GNB-CU-CP-E1AP-ID-List OPTIONAL,
-- C-ifCPUPseparated: This IE shall be present in messages from E2 Node to                           NearRT-RIC for a CP-UP separated en-gNB, whereas from NearRT-RIC to E2 Node messages, this IE may                           not be included.
    ran-UEID                    RANUEID                     OPTIONAL,
    ...
}
UEID-ENB ::= SEQUENCE{
    mME-UE-S1AP-ID              MME-UE-S1AP-ID,
    gUMMEI                      GUMMEI,
    m-eNB-UE-X2AP-ID            ENB-UE-X2AP-ID              OPTIONAL,
-- This IE shall be present in messages from E2 Node to NearRT-RIC if DC is established,                                whereas from NearRT-RIC to E2 Node messages, this IE may not be included. To be reported by MeNB                                and SeNB.
    m-eNB-UE-X2AP-ID-Extension ENB-UE-X2AP-ID-Extension     OPTIONAL,
    globalENB-ID                GlobalENB-ID                OPTIONAL,
-- This IE shall be present in messages from E2 Node to NearRT-RIC if DC is established,                                whereas from NearRT-RIC to E2 Node messages, this IE may not be included. To be reported only by                                SeNB.
    ...
}
-- **************************************************************
-- 3GPP derived IEs
--   **************************************************************
--   NOTE:
--   - Extension fields removed and replaced with "..."
--   - IE names modified across all extracts to use "PLMNIdentity"
--   **************************************************************
--   IEs derived from 3GPP 36.413 (S1AP)
--   **************************************************************
--   **************************************************************
-- copied from v16.5.0
ENB-ID ::= CHOICE {
    macro-eNB-ID    BIT STRING (SIZE (20)),
    home-eNB-ID     BIT STRING (SIZE (28)),
    ... ,
      short-Macro-eNB-ID             BIT STRING (SIZE(18)),
      long-Macro-eNB-ID              BIT STRING (SIZE(21))
}
-- copied from v16.5.0
GlobalENB-ID ::= SEQUENCE {
    pLMNIdentity            PLMNIdentity,
    eNB-ID                  ENB-ID,
    ...
}
-- copied from v16.5.0
GUMMEI           ::= SEQUENCE {
    pLMN-Identity        PLMNIdentity,
    mME-Group-ID         MME-Group-ID,
    mME-Code             MME-Code,
    ...
}
-- copied from v16.5.0
MME-Group-ID    ::= OCTET STRING (SIZE (2))
-- copied from v16.5.0
MME-Code        ::= OCTET STRING (SIZE (1))
-- copied from v16.5.0
MME-UE-S1AP-ID ::= INTEGER (0..4294967295)
-- copied from v16.5.0
QCI             ::= INTEGER (0..255)
-- copied from v16.5.0
SubscriberProfileIDforRFP ::= INTEGER (1..256)
--   **************************************************************
--   IEs derived from 3GPP 36.423 (X2AP)
--   **************************************************************
--   Extension fields removed.
--   GNB-ID renamed ENGNB-ID,
--   GlobalGNB-ID renamed GlobalenGNB-ID,
--   UE-X2AP-ID renamed ENB-UE-X2AP-ID
--   UE-X2AP-ID-Extension renamed ENB-UE-X2AP-ID-Extension
--   **************************************************************
-- copied from v16.5.0
EN-GNB-ID ::= CHOICE {
    en-gNB-ID   BIT STRING (SIZE (22..32)),
    ...
}
-- copied from v16.5.0
ENB-UE-X2AP-ID ::= INTEGER (0..4095)
-- copied from v16.5.0
ENB-UE-X2AP-ID-Extension ::= INTEGER (0..4095, ...)
-- copied from v16.5.0
E-UTRA-ARFCN ::= INTEGER (0..maxEARFCN)
-- copied from v16.5.0
E-UTRA-PCI ::= INTEGER (0..503, ...)
-- copied from v16.5.0
E-UTRA-TAC ::= OCTET STRING (SIZE(2))
-- copied from v16.5.0
GlobalenGNB-ID ::= SEQUENCE {
    pLMN-Identity           PLMNIdentity,
    en-gNB-ID               EN-GNB-ID,
    ...
}
-- **************************************************************
-- IEs derived from 3GPP 37.473 (W1AP)
-- **************************************************************
-- copied from v16.3.0
NGENB-CU-UE-W1AP-ID ::= INTEGER (0..4294967295)
-- copied from v16.3.0
NGENB-DU-ID ::= INTEGER (0..68719476735)
--   **************************************************************
--   IEs derived from 3GPP 38.413 (NGAP)
--   Extension fields removed and replaced with ...
--   **************************************************************
-- copied from v16.2.0
AMFPointer ::= BIT STRING (SIZE(6))
-- copied from v16.2.0
AMFRegionID ::= BIT STRING (SIZE(8))
-- copied from v16.2.0
AMFSetID ::= BIT STRING (SIZE(10))
-- copied from v16.2.0
AMF-UE-NGAP-ID ::= INTEGER (0..1099511627775)
-- copied from v16.2.0
EUTRACellIdentity ::= BIT STRING (SIZE(28))
-- copied from v16.2.0
EUTRA-CGI ::= SEQUENCE {
    pLMNIdentity                     PLMNIdentity,
    eUTRACellIdentity                EUTRACellIdentity,
    ...
}
-- copied from v16.2.0
FiveQI ::= INTEGER (0..255, ...)
-- copied from v16.2.0
GlobalGNB-ID ::= SEQUENCE {
    pLMNIdentity        PLMNIdentity,
    gNB-ID              GNB-ID,
    ...
}
-- copied from v16.2.0
GlobalNgENB-ID ::= SEQUENCE {
    pLMNIdentity        PLMNIdentity,
    ngENB-ID            NgENB-ID,
    ...
}
-- copied from v16.2.0
GNB-ID ::= CHOICE {
    gNB-ID      BIT STRING (SIZE(22..32)),
    ...
}
-- copied from v16.2.0
GUAMI ::= SEQUENCE {
    pLMNIdentity                PLMNIdentity,
    aMFRegionID                 AMFRegionID,
    aMFSetID                    AMFSetID,
    aMFPointer                  AMFPointer,
    ...
}
-- copied from v16.2.0
IndexToRFSP ::= INTEGER (1..256, ...)
-- copied from v16.2.0
NgENB-ID ::= CHOICE {
    macroNgENB-ID                    BIT STRING (SIZE(20)),
    shortMacroNgENB-ID               BIT STRING (SIZE(18)),
    longMacroNgENB-ID                BIT STRING (SIZE(21)),
    ...
}
-- copied from v16.2.0
NRCellIdentity ::= BIT STRING (SIZE(36))
-- copied from v16.2.0
NR-CGI ::= SEQUENCE {
    pLMNIdentity                PLMNIdentity,
    nRCellIdentity              NRCellIdentity,
    ...
}
-- copied from v16.2.0
PLMNIdentity ::= OCTET STRING (SIZE(3))
-- copied from v16.2.0
QosFlowIdentifier ::= INTEGER (0..63, ...)
-- copied from v16.2.0
SD ::= OCTET STRING (SIZE(3))
-- copied from v16.2.0
S-NSSAI ::= SEQUENCE {
    sST                         SST,
    sD                          SD                                                                    OPTIONAL,
    ...
}
-- copied from v16.2.0
SST ::= OCTET STRING (SIZE(1))
-- **************************************************************
-- IEs derived from 3GPP 38.423 (XnAP)
-- **************************************************************
-- copied from v16.2.0
NG-RANnodeUEXnAPID ::= INTEGER (0.. 4294967295)
GlobalNGRANNodeID ::= CHOICE {
    gNB                     GlobalGNB-ID,
    ng-eNB                  GlobalNgENB-ID,
    ...
}
-- **************************************************************
-- IEs derived from 3GPP 38.463 (E1AP)
-- **************************************************************
-- copied from v16.5.0
GNB-CU-CP-UE-E1AP-ID                 ::= INTEGER (0..4294967295)
-- copied from v16.5.0
GNB-CU-UP-ID                         ::= INTEGER (0..68719476735)
-- **************************************************************
-- IEs derived from 3GPP 38.473 (F1AP)
-- **************************************************************
-- copied from v16.5.0
FiveGS-TAC          ::= OCTET STRING (SIZE(3))
-- copied from v16.5.0
FreqBandNrItem      ::= SEQUENCE {
    freqBandIndicatorNr         INTEGER (1..1024, ...),
    ...
}
-- copied from v16.5.0
GNB-CU-UE-F1AP-ID   ::= INTEGER (0..4294967295)
-- copied from v16.5.0
GNB-DU-ID           ::= INTEGER (0..68719476735)
-- copied from v16.5.0
NR-PCI              ::= INTEGER (0..1007)
-- copied from v16.5.0
NR-ARFCN            ::= SEQUENCE {
    nRARFCN             INTEGER (0..maxNRARFCN),
    ...
}
-- copied from v16.5.0
NRFrequencyBand-List ::= SEQUENCE (SIZE(1..maxnoofNrCellBands)) OF NRFrequencyBandItem
-- copied from v16.5.0
NRFrequencyBandItem ::= SEQUENCE {
    freqBandIndicatorNr         INTEGER (1..1024,...),
    supportedSULBandList        SupportedSULBandList,
    ...
}
-- copied from v16.5.0
NRFrequencyInfo ::= SEQUENCE {
    nrARFCN                 NR-ARFCN,
    frequencyBand-List      NRFrequencyBand-List,
    frequencyShift7p5khz    NRFrequencyShift7p5khz                              OPTIONAL,
    ...
}
-- copied from v16.5.0
NRFrequencyShift7p5khz ::= ENUMERATED {false, true, ...}
-- copied from v16.5.0
RANUEID             ::= OCTET STRING (SIZE (8))
-- copied from v16.5.0
SupportedSULBandList ::= SEQUENCE (SIZE(0..maxnoofNrCellBands)) OF SupportedSULFreqBandItem
-- copied from v16.5.0
SupportedSULFreqBandItem ::= SEQUENCE {
    freqBandIndicatorNr         INTEGER (1..1024,...),
    ...
}

END
